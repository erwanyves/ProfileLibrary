# -*- coding: utf-8 -*-
# Path: Library/Library.FCMacro
"""
Library - Bibliothèque de composants pour FreeCAD
Point d'entrée de la macro
"""
import sys
import os

# Ajouter le répertoire de la macro au path
current_dir = os.path.dirname(os.path.abspath(__file__))
if current_dir not in sys.path:
    sys.path.insert(0, current_dir)

# Recharger le module si déjà chargé (utile pour le développement)
if 'Library' in sys.modules:
    # Supprimer tous les sous-modules
    modules_to_remove = [key for key in sys.modules.keys() if key.startswith('Library')]
    for mod in modules_to_remove:
        del sys.modules[mod]

# Importer et lancer
import Library
Library.main()
