# Chemin : Library.FCMacro
# -*- coding: utf-8 -*-
"""
Library - Bibliothèque de composants pour FreeCAD
Point d'entrée de la macro
"""
import sys
import os
import shutil

# Ajouter le répertoire de la macro au path
current_dir = os.path.dirname(os.path.abspath(__file__))
if current_dir not in sys.path:
    sys.path.insert(0, current_dir)

# ============================================================================
# Auto-installation / mise à jour de LibraryStartup dans Mod/
# ============================================================================
def _sync_startup_module():
    """Installe ou met à jour Mod/LibraryStartup depuis Library/LibraryStartup.

    Compare les fichiers par hash SHA-256.
    Retourne True si la macro peut continuer, False si un redémarrage est requis.
    """
    import hashlib

    def _file_hash(path):
        h = hashlib.sha256()
        with open(path, "rb") as f:
            for chunk in iter(lambda: f.read(8192), b""):
                h.update(chunk)
        return h.hexdigest()

    try:
        import FreeCAD as App
        from PySide import QtGui

        src_dir = os.path.join(current_dir, "Library", "LibraryStartup")
        if not os.path.isdir(src_dir):
            return True  # Pas de source, continuer

        mod_dir = os.path.join(App.ConfigGet("UserAppData"), "Mod")
        dest_dir = os.path.join(mod_dir, "LibraryStartup")

        # Lister les fichiers source (ignorer __pycache__, .pyc, fichiers cachés)
        src_files = {}
        for name in os.listdir(src_dir):
            fp = os.path.join(src_dir, name)
            if os.path.isfile(fp) and not name.startswith(".") and not name.endswith(".pyc"):
                src_files[name] = fp

        is_new_install = not os.path.isdir(dest_dir)
        needs_update = is_new_install

        if not is_new_install:
            for name, src_path in src_files.items():
                dest_path = os.path.join(dest_dir, name)
                if not os.path.isfile(dest_path):
                    needs_update = True
                    break
                if _file_hash(src_path) != _file_hash(dest_path):
                    needs_update = True
                    break

        if not needs_update:
            return True  # Tout est à jour, continuer

        # Copier / écraser
        os.makedirs(dest_dir, exist_ok=True)
        for name, src_path in src_files.items():
            shutil.copy2(src_path, os.path.join(dest_dir, name))

        action = "installé" if is_new_install else "mis à jour"
        App.Console.PrintMessage(
            f"Library - LibraryStartup {action} dans Mod/\n"
        )
        QtGui.QMessageBox.information(
            None,
            "Macro Library",
            f"Le module LibraryStartup a été {action}.\n"
            "Redémarrez FreeCAD pour appliquer les modifications.\n\n"
            "La macro ne sera pas lancée cette fois-ci."
        )
        return False  # Redémarrage requis, stopper la macro

    except Exception as e:
        print(f"Library - Erreur sync LibraryStartup: {e}")
        return True  # En cas d'erreur, laisser continuer

_can_continue = _sync_startup_module()

# ============================================================================
# Lancement de la macro (seulement si pas de mise à jour en attente)
# ============================================================================
if _can_continue:
    # Recharger le module si déjà chargé (utile pour le développement)
    if 'Library' in sys.modules:
        modules_to_remove = [key for key in sys.modules.keys() if key.startswith('Library')]
        for mod in modules_to_remove:
            del sys.modules[mod]

    # Importer et lancer
    import Library
    Library.main()
